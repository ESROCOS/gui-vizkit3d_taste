Context-vizkit3d-trajectory DEFINITIONS ::=
BEGIN
   IMPORTS
      Vizkit3D-FilePath FROM Vizkit3D-Types
      Vizkit3D-PluginLabel FROM Vizkit3D-Types;

--  Group all context parameters of this function in a record
Context-vizkit3d-trajectory ::= SEQUENCE {
   configfile Vizkit3D-FilePath,
   id Vizkit3D-PluginLabel

}

--  Declare a constant with the values set by the user in the interface view
vizkit3d-trajectory-ctxt Context-vizkit3d-trajectory ::= {
   configfile "config-trajectory.yml",
   id "Trajectory"

}
END
