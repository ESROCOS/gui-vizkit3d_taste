-- H2020 ESROCOS Project
-- Company: GMV Aerospace & Defence S.A.U.
-- Licence: GPLv2

Vizkit3D-Types DEFINITIONS ::=
BEGIN

IMPORTS 
T-UInt32 FROM TASTE-BasicTypes;

-- String sizes
vizkit3d-PathMaxSize T-UInt32 ::= 255
vizkit3d-LabelMaxSize T-UInt32 ::= 31


-- File path, used for configuration files
Vizkit3D-FilePath ::= IA5String (SIZE (0..vizkit3d-PathMaxSize))

-- Plugin label, identifies a plugin in a configuration file
Vizkit3D-PluginLabel ::= IA5String (SIZE (1..vizkit3d-LabelMaxSize))

END
